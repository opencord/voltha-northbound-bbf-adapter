module bbf-voltha-vlan-translation {
  yang-version 1.1;

  namespace "urn:bbf:yang:bbf-voltha-vlan-translation";
  prefix bbf-voltha-vlan-tr;

  import bbf-l2-access-attributes {
    prefix bbf-l2access-attr;
  }
  import bbf-dot1q-types {
    prefix bbf-dot1qt;
  }

  organization
    "Broadband Forum <https://www.broadband-forum.org>
     SDN/NFV Work Area";
  contact
    "Comments or questions about this Broadband Forum YANG module
     should be directed to <mailto:help@broadband-forum.org>.

     Editor:      TBD

     WA Director: Mengmeng Li, China Mobile

     WA Director: Bruno Cornaglia, Vodafone";
  description
    "TBD.

     Copyright (c) 2019-2022, Broadband Forum

     Redistribution and use in source and binary forms, with or
     without modification, are permitted provided that the following
     conditions are met:

     1. Redistributions of source code must retain the above copyright
        notice, this list of conditions and the following disclaimer.

     2. Redistributions in binary form must reproduce the above
        copyright notice, this list of conditions and the following
        disclaimer in the documentation and/or other materials
        provided with the distribution.

     3. Neither the name of the copyright holder nor the names of its
        contributors may be used to endorse or promote products
        derived from this software without specific prior written
        permission.

     THIS SOFTWARE IS PROVIDED BY THE COPYRIGHT HOLDERS AND
     CONTRIBUTORS \"AS IS\" AND ANY EXPRESS OR IMPLIED WARRANTIES,
     INCLUDING, BUT NOT LIMITED TO, THE IMPLIED WARRANTIES OF
     MERCHANTABILITY AND FITNESS FOR A PARTICULAR PURPOSE ARE
     DISCLAIMED. IN NO EVENT SHALL THE COPYRIGHT HOLDER OR
     CONTRIBUTORS BE LIABLE FOR ANY DIRECT, INDIRECT, INCIDENTAL,
     SPECIAL, EXEMPLARY, OR CONSEQUENTIAL DAMAGES (INCLUDING, BUT
     NOT LIMITED TO, PROCUREMENT OF SUBSTITUTE GOODS OR SERVICES;
     LOSS OF USE, DATA, OR PROFITS; OR BUSINESS INTERRUPTION) HOWEVER
     CAUSED AND ON ANY THEORY OF LIABILITY, WHETHER IN CONTRACT,
     STRICT LIABILITY, OR TORT (INCLUDING NEGLIGENCE OR OTHERWISE)
     ARISING IN ANY WAY OUT OF THE USE OF THIS SOFTWARE, EVEN IF
     ADVISED OF THE POSSIBILITY OF SUCH DAMAGE.

     The above license is used as a license under copyright only.
     Please reference the Forum IPR Policy for patent licensing terms
     <https://www.broadband-forum.org/ipr-policy>.

     Any moral rights which are necessary to exercise under the above
     license grant are also deemed granted under this license.

     This version of this YANG module is part of TR-451; see
     the TR itself for full legal notices.";

  revision 2022-03-22 {
    description
      "Initial revision.";
    reference
      "TBD";
  }

  augment "/bbf-l2access-attr:vlan-translation-profiles"
    + "/bbf-l2access-attr:vlan-translation-profile"
    + "/bbf-l2access-attr:ingress-rewrite"
    + "/bbf-l2access-attr:push-outer-tag" {
    description
      "Augmentation of the vlan translation profile outer tag with
       downstream pbit";
    
    leaf d-pbit {
      type union {
        type bbf-dot1qt:pbit-list;
        type enumeration {
          enum any {
            description
              "Matches any pbit value in the range of 0 to 7.";
          }
        }
      }
      description
        "Allowed downstream PBIT values.";
    }
  }

  augment "/bbf-l2access-attr:vlan-translation-profiles"
    + "/bbf-l2access-attr:vlan-translation-profile"
    + "/bbf-l2access-attr:ingress-rewrite"
    + "/bbf-l2access-attr:push-second-tag" {
    description
      "Augmentation of the vlan translation profile second tag with
       downstream pbit";
    
    leaf d-pbit {
      type union {
        type bbf-dot1qt:pbit-list;
        type enumeration {
          enum any {
            description
              "Matches any pbit value in the range of 0 to 7.";
          }
        }
      }
      description
        "Allowed downstream PBIT values.";
    }
  }
}
